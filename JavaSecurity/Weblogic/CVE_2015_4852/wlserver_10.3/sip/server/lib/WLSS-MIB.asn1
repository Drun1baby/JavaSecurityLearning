WLSS-MIB DEFINITIONS ::= BEGIN
IMPORTS

  Counter64
    FROM SNMPv2-SMI
	enterprises, Counter
		FROM RFC1155-SMI
	OBJECT-TYPE
		FROM RFC-1212
	DisplayString
		FROM RFC1213-MIB
	TRAP-TYPE
		FROM RFC-1215;
bea	OBJECT IDENTIFIER  ::=  {  enterprises  140  }

wls	OBJECT IDENTIFIER  ::=  {  bea  625  }

wlss	OBJECT IDENTIFIER  ::=  {  bea  626  }

sipServerTable	OBJECT-TYPE
	SYNTAX	SEQUENCE  OF  SipServerEntry
	MAX-ACCESS	not-accessible
	STATUS	current
 	::=  { wlss  1 }

sipServerEntry	OBJECT-TYPE
	SYNTAX	SipServerEntry
	MAX-ACCESS	not-accessible
	STATUS	current
 	INDEX	{  sipServerIndex  }
	::=  { sipServerTable 1 }

SipServerEntry  ::=  SEQUENCE {
	sipServerIndex  DisplayString,
	sipServerT1TimeoutInterval  INTEGER,
	sipServerT2TimeoutInterval  INTEGER,
	sipServerT4TimeoutInterval  INTEGER,
	sipServerTimerBTimeoutInterval  INTEGER,
	sipServerTimerFTimeoutInterval  INTEGER,
	sipServerMaxApplicationSessionLifetime  DisplayString,
	sipServerDefaultBehavior  DisplayString,
	sipServerEnableLocalDispatch  DisplayString,
	sipServerDefaultServletName  DisplayString,
	sipServerEnableContactProvisionalResponse  DisplayString,
	sipServerEnableDnsSrvLookup  DisplayString,
	sipServerEnableRport  DisplayString,
	sipServerEngineCallStateCacheEnabled  DisplayString,
	sipServerGloballyRoutableUri  DisplayString,
	sipServerImageDumpLevel  DisplayString,
	sipServerRetryAfterValue  DisplayString,
	sipServerServerHeader  DisplayString,
	sipServerServerHeaderValue  DisplayString,
	sipServerStaleSessionHandling  DisplayString,
	sipServerUseHeaderForm  DisplayString
	}

sipServerIndex	OBJECT-TYPE 
	SYNTAX	DisplayString 
	MAX-ACCESS	read-only 
	STATUS	current
	::=  {  sipServerEntry  1  }

sipServerT1TimeoutInterval	OBJECT-TYPE 
	SYNTAX	INTEGER 
	MAX-ACCESS	read-only 
	STATUS	current
	::=  {  sipServerEntry  2  }

sipServerT2TimeoutInterval	OBJECT-TYPE 
	SYNTAX	INTEGER 
	MAX-ACCESS	read-only 
	STATUS	current
	::=  {  sipServerEntry  3  }

sipServerT4TimeoutInterval	OBJECT-TYPE 
	SYNTAX	INTEGER 
	MAX-ACCESS	read-only 
	STATUS	current
	::=  {  sipServerEntry  4  }

sipServerTimerBTimeoutInterval	OBJECT-TYPE 
	SYNTAX	INTEGER 
	MAX-ACCESS	read-only 
	STATUS	current
	::=  {  sipServerEntry  5  }

sipServerTimerFTimeoutInterval	OBJECT-TYPE 
	SYNTAX	INTEGER 
	MAX-ACCESS	read-only 
	STATUS	current
	::=  {  sipServerEntry  6  }

sipServerMaxApplicationSessionLifetime	OBJECT-TYPE 
	SYNTAX	INTEGER 
	MAX-ACCESS	read-only 
	STATUS	current
	DESCRIPTION
		"Max application session life time in minutes"
	::=  {  sipServerEntry  7  }

sipServerDefaultBehavior	OBJECT-TYPE 
	SYNTAX	DisplayString 
	MAX-ACCESS	read-only 
	STATUS	current
	DESCRIPTION
		"Default behavior ua or proxy"
	::=  {  sipServerEntry  8  }

sipServerEnableLocalDispatch	OBJECT-TYPE 
	SYNTAX	DisplayString 
	MAX-ACCESS	read-only 
	STATUS	current
	DESCRIPTION
		"Enable local dispatch 1 means true 0 means false"
	::=  {  sipServerEntry  9  }

sipServerDefaultServletName	OBJECT-TYPE 
	SYNTAX	DisplayString 
	MAX-ACCESS	read-only 
	STATUS	current
	DESCRIPTION
		"Default servlet name"
	::=  {  sipServerEntry  10  }

sipServerEnableContactProvisionalResponse	OBJECT-TYPE 
	SYNTAX	DisplayString 
	MAX-ACCESS	read-only 
	STATUS	current
	DESCRIPTION
		"Specifies whether the server puts Contact Header in non-reliable provisonal(1xx) response having To tag"
	::=  {  sipServerEntry  11  }

sipServerEnableDnsSrvLookup	OBJECT-TYPE 
	SYNTAX	DisplayString 
	MAX-ACCESS	read-only 
	STATUS	current
	DESCRIPTION
		"Specifies whether the server performs DNS lookup."
	::=  {  sipServerEntry  12  }

sipServerEnableRport	OBJECT-TYPE 
	SYNTAX	DisplayString 
	MAX-ACCESS	read-only 
	STATUS	current
	DESCRIPTION
		"Specifies whether symmetric response routing is requested"
	::=  {  sipServerEntry  13  }

sipServerEngineCallStateCacheEnabled	OBJECT-TYPE 
	SYNTAX	DisplayString 
	MAX-ACCESS	read-only 
	STATUS	current
	DESCRIPTION
		"Specifies whether engines cache a portion of the call state data locally."
	::=  {  sipServerEntry  14  }

sipServerGloballyRoutableUri	OBJECT-TYPE 
	SYNTAX	DisplayString 
	MAX-ACCESS	read-only 
	STATUS	current
	DESCRIPTION
		"A Globally-Routable User Agent URI (GRUU)"
	::=  {  sipServerEntry  15  }

sipServerImageDumpLevel  OBJECT-TYPE 
	SYNTAX	DisplayString 
	MAX-ACCESS	read-only 
	STATUS	current
	DESCRIPTION
		"Specifies the level of detail to be recorded in diagnostic image files."
	::=  {  sipServerEntry  16  }

sipServerRetryAfterValue  OBJECT-TYPE 
	SYNTAX	DisplayString 
	MAX-ACCESS	read-only 
	STATUS	current
	DESCRIPTION
		"The number of seconds used in the Retry-After header for 5xx responses."
	::=  {  sipServerEntry  17  }

sipServerServerHeader  OBJECT-TYPE 
	SYNTAX	DisplayString 
	MAX-ACCESS	read-only 
	STATUS	current
	DESCRIPTION
		"Specifies the conditions for inserting a Server header into SIP messages"
	::=  {  sipServerEntry  18  }

sipServerServerHeaderValue  OBJECT-TYPE 
	SYNTAX	DisplayString 
	MAX-ACCESS	read-only 
	STATUS	current
	DESCRIPTION
		"The value of the Server header inserted into SIP messages."
	::=  {  sipServerEntry  19  }

sipServerStaleSessionHandling  OBJECT-TYPE 
	SYNTAX	DisplayString 
	MAX-ACCESS	read-only 
	STATUS	current
	DESCRIPTION
		"The action to perform when an incoming message contains erroneous session identifiers."
	::=  {  sipServerEntry  20  }

sipServerUseHeaderForm  OBJECT-TYPE 
	SYNTAX	DisplayString 
	MAX-ACCESS	read-only 
	STATUS	current
	DESCRIPTION
		"Specifies how the server applies rules for compacting SIP message headers."
	::=  {  sipServerEntry  21  }


proxyTable	OBJECT-TYPE
	SYNTAX	SEQUENCE  OF  ProxyEntry
	MAX-ACCESS	not-accessible
	STATUS	current
 	::=  { wlss  2 }

proxyEntry	OBJECT-TYPE
	SYNTAX	ProxyEntry
	MAX-ACCESS	not-accessible
	STATUS	current
 	INDEX	{  proxyIndex  }
	::=  { proxyTable 1 }

ProxyEntry  ::=  SEQUENCE {
	proxyIndex  DisplayString,
	proxyRoutingPolicy  DisplayString,
	proxyUris  DisplayString
	}

proxyIndex	OBJECT-TYPE 
	SYNTAX	DisplayString 
	MAX-ACCESS	read-only 
	STATUS	current
	::=  {  proxyEntry  1  }

proxyRoutingPolicy	OBJECT-TYPE 
	SYNTAX	DisplayString 
	MAX-ACCESS	read-only 
	STATUS	current
	::=  {  proxyEntry  2  }

proxyUris	OBJECT-TYPE 
	SYNTAX	DisplayString 
	MAX-ACCESS	read-only 
	STATUS	current
	::=  {  proxyEntry  3  }


overloadTable	OBJECT-TYPE
	SYNTAX	SEQUENCE  OF  OverloadEntry
	MAX-ACCESS	not-accessible
	STATUS	current
 	::=  { wlss  3 }

overloadEntry	OBJECT-TYPE
	SYNTAX	OverloadEntry
	MAX-ACCESS	not-accessible
	STATUS	current
 	INDEX	{  overloadIndex  }
	::=  { overloadTable 1 }

OverloadEntry  ::=  SEQUENCE {
	overloadIndex  DisplayString,
	overloadThresholdPolicy  DisplayString,
	overloadThresholdValue  Counter32,
	overloadReleaseValue  Counter32
	}
	
overloadIndex	OBJECT-TYPE
	SYNTAX	DisplayString 
	MAX-ACCESS	read-only 
	STATUS	current
	::=  {  overloadEntry  1  }

overloadThresholdPolicy	OBJECT-TYPE
	SYNTAX	DisplayString 
	MAX-ACCESS	read-only 
	STATUS	current
	::=  {  overloadEntry  2  }

overloadThresholdValue	OBJECT-TYPE
	SYNTAX	Counter32 
	MAX-ACCESS	read-only 
	STATUS	current
	::=  {  overloadEntry  3  }

overloadReleaseValue	OBJECT-TYPE
	SYNTAX	Counter32 
	MAX-ACCESS	read-only 
	STATUS	current
	::=  {  overloadEntry  4  }


partitionTable	OBJECT-TYPE
	SYNTAX	SEQUENCE  OF  PartitionEntry
	MAX-ACCESS	not-accessible
	STATUS	current
 	::=  { wlss  4 }

partitionEntry	OBJECT-TYPE
	SYNTAX	PartitionEntry
	MAX-ACCESS	not-accessible
	STATUS	current
 	INDEX	{  partitionIndex  }
	::=  { partitionTable 1 }

PartitionEntry  ::=  SEQUENCE {
	partitionIndex  DisplayString,
	partitionServerNames  DisplayString
	}

partitionIndex	OBJECT-TYPE
	SYNTAX	DisplayString 
	MAX-ACCESS	read-only 
	STATUS	current
	::=  {  partitionEntry  1  }

partitionServerNames	OBJECT-TYPE
	SYNTAX	DisplayString 
	MAX-ACCESS	read-only 
	STATUS	current
	DESCRIPTION
		"Array of servers"
	::=  {  partitionEntry  2  }


messageDebugTable	OBJECT-TYPE
	SYNTAX	SEQUENCE  OF  MessageDebugEntry
	MAX-ACCESS	not-accessible
	STATUS	current
 	::=  { wlss  5 }

messageDebugEntry	OBJECT-TYPE
	SYNTAX	MessageDebugEntry
	MAX-ACCESS	not-accessible
	STATUS	current
 	INDEX	{  messageDebugIndex  }
	::=  { messageDebugTable 1 }

MessageDebugEntry  ::=  SEQUENCE {
	messageDebugIndex  DisplayString,
	messageDebugLevel  DisplayString,
	messageDebugPattern  DisplayString,
	messageDebugTokens  DisplayString
	}

messageDebugIndex	OBJECT-TYPE
	SYNTAX	DisplayString 
	MAX-ACCESS	read-only 
	STATUS	current
	::=  {  messageDebugEntry  1  }

messageDebugLevel	OBJECT-TYPE
	SYNTAX	DisplayString 
	MAX-ACCESS	read-only 
	STATUS	current
	::=  {  messageDebugEntry  2  }

messageDebugPattern	OBJECT-TYPE
	SYNTAX	DisplayString 
	MAX-ACCESS	read-only 
	STATUS	current
	::=  {  messageDebugEntry  3  }

messageDebugTokens	OBJECT-TYPE
	SYNTAX	DisplayString 
	MAX-ACCESS	read-only 
	STATUS	current
	::=  {  messageDebugEntry  4  }


clusterLoadbalancerMapTable	OBJECT-TYPE
	SYNTAX	SEQUENCE  OF  ClusterLoadbalancerMapEntry
	MAX-ACCESS	not-accessible
	STATUS	current
 	::=  { wlss  6 }

clusterLoadbalancerMapEntry	OBJECT-TYPE
	SYNTAX	ClusterLoadbalancerMapEntry
	MAX-ACCESS	not-accessible
	STATUS	current
 	INDEX	{  clusterLoadbalancerMapIndex  }
	::=  { clusterLoadbalancerMapTable 1 }

ClusterLoadbalancerMapEntry  ::=  SEQUENCE {
	clusterLoadbalancerMapIndex  DisplayString,
	clusterLoadbalancerMapClusterName  DisplayString,
	clusterLoadbalancerMapSipUri  DisplayString
	}

clusterLoadbalancerMapIndex	OBJECT-TYPE
	SYNTAX	DisplayString 
	MAX-ACCESS	read-only 
	STATUS	current
	::=  {  clusterLoadbalancerMapEntry  1  }

clusterLoadbalancerMapClusterName	OBJECT-TYPE
	SYNTAX	DisplayString 
	MAX-ACCESS	read-only 
	STATUS	current
	::=  {  clusterLoadbalancerMapEntry  2  }

clusterLoadbalancerMapSipUri	OBJECT-TYPE
	SYNTAX	DisplayString 
	MAX-ACCESS	read-only 
	STATUS	current
	::=  {  clusterLoadbalancerMapEntry  3  }


sipSecurityTable	OBJECT-TYPE
	SYNTAX	SEQUENCE  OF  SipSecurityEntry
	MAX-ACCESS	not-accessible
	STATUS	current
 	::=  { wlss  7 }

sipSecurityEntry	OBJECT-TYPE
	SYNTAX	SipSecurityEntry
	MAX-ACCESS	not-accessible
	STATUS	current
 	INDEX	{  sipSecurityIndex  }
	::=  { sipSecurityTable 1 }

SipSecurityEntry  ::=  SEQUENCE {
	sipSecurityIndex  DisplayString,
	sipSecurityTrustedAuthenticationHosts  DisplayString,
	sipSecurityTrustedChargingHosts  DisplayString
	}

sipSecurityIndex	OBJECT-TYPE
	SYNTAX	DisplayString 
	MAX-ACCESS	read-only 
	STATUS	current
	::=  {  sipSecurityEntry  1  }

sipSecurityTrustedAuthenticationHosts	OBJECT-TYPE
	SYNTAX	DisplayString 
	MAX-ACCESS	read-only 
	STATUS	current
	::=  {  sipSecurityEntry  2  }

sipSecurityTrustedChargingHosts	OBJECT-TYPE
	SYNTAX	DisplayString 
	MAX-ACCESS	read-only 
	STATUS	current
	::=  {  sipSecurityEntry  3  }


sipServerRuntimeTable	OBJECT-TYPE
	SYNTAX	SEQUENCE  OF  SipServerRuntimeEntry
	MAX-ACCESS	not-accessible
	STATUS	current
 	::=  { wlss  8 }

sipServerRuntimeEntry	OBJECT-TYPE
	SYNTAX	SipServerRuntimeEntry
	MAX-ACCESS	not-accessible
	STATUS	current
 	INDEX	{  sipServerRuntimeIndex  }
	::=  { sipServerRuntimeTable 1 }

SipServerRuntimeEntry  ::=  SEQUENCE {
	sipServerRuntimeIndex  DisplayString,
	sipServerRuntimeServerAppSessionCount  Counter32,
	sipServerRuntimeServerSipSessionCount  Counter32,
	sipServerRuntimeStartTime  Counter64,
	sipServerRuntimeActiveServerAppSessionCount  Counter64,
	sipServerRuntimeActiveServerSipSessionCount  Counter64,
	sipServerRuntimeMessagesProcessed  Counter64,
	sipServerRuntimeMessagesRejected  Counter64,
	sipServerRuntimeMessagesReceived  Counter64,
	sipServerRuntimeDestroyedServerAppSessionCount Counter64,
  	sipServerRuntimeDestroyedServerSipSessionCount Counter64,
  	sipServerRuntimeClusterId Counter64
	}

sipServerRuntimeIndex	OBJECT-TYPE
	SYNTAX	DisplayString 
	MAX-ACCESS	read-only 
	STATUS	current
	::=  {  sipServerRuntimeEntry  1  }

sipServerRuntimeServerAppSessionCount	OBJECT-TYPE
	SYNTAX	Counter32 
	MAX-ACCESS	read-only 
	STATUS	current
	::=  {  sipServerRuntimeEntry  2  }

sipServerRuntimeServerSipSessionCount	OBJECT-TYPE
	SYNTAX	Counter32 
	MAX-ACCESS	read-only 
	STATUS	current
	::=  {  sipServerRuntimeEntry  3  }

sipServerRuntimeStartTime	OBJECT-TYPE
	SYNTAX	Counter64 
	MAX-ACCESS	read-only 
	STATUS	current
	::=  {  sipServerRuntimeEntry  4  }

sipServerRuntimeActiveServerAppSessionCount	OBJECT-TYPE
	SYNTAX	Counter64 
	MAX-ACCESS	read-only 
	STATUS	current
	::=  {  sipServerRuntimeEntry  5  }

sipServerRuntimeActiveServerSipSessionCount	OBJECT-TYPE
	SYNTAX	Counter64 
	MAX-ACCESS	read-only 
	STATUS	current
	::=  {  sipServerRuntimeEntry  6  }

sipServerRuntimeMessagesProcessed	OBJECT-TYPE
	SYNTAX	Counter64 
	MAX-ACCESS	read-only 
	STATUS	current
	::=  {  sipServerRuntimeEntry  7  }

sipServerRuntimeMessagesRejected	OBJECT-TYPE
	SYNTAX	Counter64 
	MAX-ACCESS	read-only 
	STATUS	current
	::=  {  sipServerRuntimeEntry  8  }

sipServerRuntimeMessagesReceived	OBJECT-TYPE
	SYNTAX	Counter64 
	MAX-ACCESS	read-only 
	STATUS	current
	::=  {  sipServerRuntimeEntry  9  }

sipServerRuntimeDestroyedServerAppSessionCount	OBJECT-TYPE
	SYNTAX	Counter64
	MAX-ACCESS	read-only
	STATUS	current
	::=  {  sipServerRuntimeEntry  10  }

sipServerRuntimeDestroyedServerSipSessionCount	OBJECT-TYPE
	SYNTAX	Counter64
	MAX-ACCESS	read-only
	STATUS	current
	::=  {  sipServerRuntimeEntry  11  }

sipServerRuntimeClusterId	OBJECT-TYPE
	SYNTAX	Counter64
	MAX-ACCESS	read-only
	STATUS	current
	::=  {  sipServerRuntimeEntry  12  }


sipApplicationRuntimeTable	OBJECT-TYPE
	SYNTAX	SEQUENCE  OF  SipApplicationRuntimeEntry
	MAX-ACCESS	not-accessible
	STATUS	current
 	::=  { wlss  9 }

sipApplicationRuntimeEntry	OBJECT-TYPE
	SYNTAX	SipApplicationRuntimeEntry
	MAX-ACCESS	not-accessible
	STATUS	current
 	INDEX	{  sipApplicationRuntimeIndex  }
	::=  { sipApplicationRuntimeTable 1 }

SipApplicationRuntimeEntry  ::=  SEQUENCE {
	sipApplicationRuntimeIndex  DisplayString,
	sipApplicationRuntimeAppSessionCount  Counter32,
	sipApplicationRuntimeSipSessionCount  Counter32,
	sipApplicationRuntimeActiveAppSessionCount  Counter64,
	sipApplicationRuntimeActiveSipSessionCount  Counter32,
	sipApplicationRuntimeDestroyedAppSessionCount  Counter64,
	sipApplicationRuntimeDestroyedSipSessionCount  Counter64,
	sipApplicationRuntimeEngine  DisplayString
	}

sipApplicationRuntimeIndex	OBJECT-TYPE
	SYNTAX	DisplayString
	MAX-ACCESS	read-only
	STATUS	current
	::=  {  sipApplicationRuntimeEntry  1  }

sipApplicationRuntimeAppSessionCount	OBJECT-TYPE
	SYNTAX	Counter32
	MAX-ACCESS	read-only
	STATUS	current
	::=  {  sipApplicationRuntimeEntry  2  }

sipApplicationRuntimeSipSessionCount	OBJECT-TYPE
	SYNTAX	Counter32
	MAX-ACCESS	read-only
	STATUS	current
	::=  {  sipApplicationRuntimeEntry  3  }

sipApplicationRuntimeActiveAppSessionCount	OBJECT-TYPE
	SYNTAX	Counter64
	MAX-ACCESS	read-only
	STATUS	current
	::=  {  sipApplicationRuntimeEntry  4  }

sipApplicationRuntimeActiveSipSessionCount	OBJECT-TYPE
	SYNTAX	Counter32
	MAX-ACCESS	read-only
	STATUS	current
	::=  {  sipApplicationRuntimeEntry  5  }

sipApplicationRuntimeDestroyedAppSessionCount	OBJECT-TYPE
	SYNTAX	Counter64
	MAX-ACCESS	read-only
	STATUS	current
	::=  {  sipApplicationRuntimeEntry  6  }

sipApplicationRuntimeDestroyedSipSessionCount	OBJECT-TYPE
	SYNTAX	Counter64
	MAX-ACCESS	read-only
	STATUS	current
	::=  {  sipApplicationRuntimeEntry  7  }

sipApplicationRuntimeEngine	OBJECT-TYPE
	SYNTAX	DisplayString
	MAX-ACCESS	read-only
	STATUS	current
	::=  {  sipApplicationRuntimeEntry  8  }

replicaRuntimeTable	OBJECT-TYPE
	SYNTAX	SEQUENCE  OF  ReplicaRuntimeEntry
	MAX-ACCESS	not-accessible
	STATUS	current
 	::=  { wlss  10 }

replicaRuntimeEntry	OBJECT-TYPE
	SYNTAX	ReplicaRuntimeEntry
	MAX-ACCESS	not-accessible
	STATUS	current
 	INDEX	{  replicaRuntimeIndex  }
	::=  { replicaRuntimeTable 1 }

ReplicaRuntimeEntry  ::=  SEQUENCE {
	replicaRuntimeIndex  DisplayString,
	replicaRuntimeReplicaName  DisplayString,
	replicaRuntimePartitionName  DisplayString,
	replicaRuntimeState  DisplayString,
	replicaRuntimeCurrentViewId  INTEGER,
	replicaRuntimeReplicaServersInCurrentView  DisplayString,
	replicaRuntimeTimerQueueSize  INTEGER,
	replicaRuntimeKeyCount  INTEGER,
	replicaRuntimeHighKeyCount  INTEGER,
	replicaRuntimeDataItemCount  INTEGER,
	replicaRuntimeDataItemsToRecover  INTEGER,
	replicaRuntimeTotalBytes  Counter64,
	replicaRuntimeHighTotalBytes  Counter64,
	replicaRuntimeBytesReceived  Counter64,
	replicaRuntimeBytesSent  Counter64
	}

replicaRuntimeIndex	OBJECT-TYPE 
	SYNTAX	DisplayString 
	MAX-ACCESS	read-only 
	STATUS	current
	::=  {  replicaRuntimeEntry  1  }

replicaRuntimeReplicaName	OBJECT-TYPE
	SYNTAX	DisplayString 
	MAX-ACCESS	read-only 
	STATUS	current
	::=  {  replicaRuntimeEntry  2  }

replicaRuntimePartitionName	OBJECT-TYPE
	SYNTAX	DisplayString 
	MAX-ACCESS	read-only 
	STATUS	current
	::=  {  replicaRuntimeEntry  3  }

replicaRuntimeState	OBJECT-TYPE
	SYNTAX	DisplayString 
	MAX-ACCESS	read-only 
	STATUS	current
	::=  {  replicaRuntimeEntry  4  }

replicaRuntimeCurrentViewId	OBJECT-TYPE
	SYNTAX	INTEGER 
	MAX-ACCESS	read-only 
	STATUS	current
	DESCRIPTION
		"Number of times replica view has changed since server started"
	::=  {  replicaRuntimeEntry  5  }

replicaRuntimeReplicaServersInCurrentView	OBJECT-TYPE
	SYNTAX	DisplayString 
	MAX-ACCESS	read-only 
	STATUS	current
	::=  {  replicaRuntimeEntry  6  }

replicaRuntimeTimerQueueSize	OBJECT-TYPE
	SYNTAX	INTEGER 
	MAX-ACCESS	read-only 
	STATUS	current
	::=  {  replicaRuntimeEntry  7  }

replicaRuntimeKeyCount	OBJECT-TYPE
	SYNTAX	INTEGER 
	MAX-ACCESS	read-only 
	STATUS	current
	::=  {  replicaRuntimeEntry  8  }

replicaRuntimeHighKeyCount	OBJECT-TYPE
	SYNTAX	INTEGER 
	MAX-ACCESS	read-only 
	STATUS	current
	::=  {  replicaRuntimeEntry  9  }

replicaRuntimeDataItemCount	OBJECT-TYPE
	SYNTAX	INTEGER 
	MAX-ACCESS	read-only 
	STATUS	current
	::=  {  replicaRuntimeEntry  10  }

replicaRuntimeDataItemsToRecover	OBJECT-TYPE
	SYNTAX	INTEGER 
	MAX-ACCESS	read-only 
	STATUS	current
	::=  {  replicaRuntimeEntry  11  }

replicaRuntimeTotalBytes	OBJECT-TYPE
	SYNTAX	Counter64
	MAX-ACCESS	read-only 
	STATUS	current
	::=  {  replicaRuntimeEntry  12  }

replicaRuntimeHighTotalBytes	OBJECT-TYPE
	SYNTAX	Counter64
	MAX-ACCESS	read-only 
	STATUS	current
	::=  {  replicaRuntimeEntry  13  }

replicaRuntimeBytesReceived	OBJECT-TYPE
	SYNTAX	Counter64 
	MAX-ACCESS	read-only 
	STATUS	current
	DESCRIPTION
		"bytes received"
	::=  {  replicaRuntimeEntry  14  }

replicaRuntimeBytesSent	OBJECT-TYPE
	SYNTAX	Counter64 
	MAX-ACCESS	read-only 
	STATUS	current
	::=  {  replicaRuntimeEntry  15  }


connectionReusePoolTable	OBJECT-TYPE
	SYNTAX	SEQUENCE  OF  ConnectionReusePoolEntry
	MAX-ACCESS	not-accessible
	STATUS	current
 	::=  { wlss  11 }

connectionReusePoolEntry	OBJECT-TYPE
	SYNTAX	ConnectionReusePoolEntry
	MAX-ACCESS	not-accessible
	STATUS	current
 	INDEX	{  connectionReusePoolIndex  }
	::=  { connectionReusePoolTable 1 }

ConnectionReusePoolEntry  ::=  SEQUENCE {
	connectionReusePoolIndex  DisplayString,
	connectionReusePoolPoolName  DisplayString,
	connectionReusePoolDestination  DisplayString,
	connectionReusePoolDestinationPort INTEGER,
	connectionReusePoolMaximumConnections INTEGER
	}

connectionReusePoolIndex	OBJECT-TYPE
	SYNTAX	DisplayString 
	MAX-ACCESS	read-only 
	STATUS	current
	::=  {  connectionReusePoolEntry  1  }

connectionReusePoolPoolName	OBJECT-TYPE
	SYNTAX	DisplayString 
	MAX-ACCESS	read-only 
	STATUS	current
	::=  {  connectionReusePoolEntry  2  }

connectionReusePoolDestination	OBJECT-TYPE
	SYNTAX	DisplayString 
	MAX-ACCESS	read-only 
	STATUS	current
	::=  {  connectionReusePoolEntry  3  }

connectionReusePoolDestinationPort	OBJECT-TYPE
	SYNTAX	INTEGER
	MAX-ACCESS	read-only 
	STATUS	current
	::=  {  connectionReusePoolEntry  4  }

connectionReusePoolMaximumConnections OBJECT-TYPE
	SYNTAX	INTEGER
	MAX-ACCESS	read-only 
	STATUS	current
	::=  {  connectionReusePoolEntry  5  }


persistenceTable	OBJECT-TYPE
	SYNTAX	SEQUENCE  OF  PersistenceEntry
	MAX-ACCESS	not-accessible
	STATUS	current
 	::=  { wlss  12 }

persistenceEntry	OBJECT-TYPE
	SYNTAX	PersistenceEntry
	MAX-ACCESS	not-accessible
	STATUS	current
 	INDEX	{  persistenceIndex  }
	::=  { persistenceTable 1 }

PersistenceEntry  ::=  SEQUENCE {
	persistenceIndex  DisplayString,
	persistenceDefaultHandling  DisplayString,
	persistenceGeoSiteId  INTEGER,
	persistenceGeoRemoteT3Url  DisplayString,
	persistenceDbEnabled  DisplayString,
	persistenceGeoEnabled  DisplayString,
	persistenceJmsSendAsIdentity  DisplayString
	}

persistenceIndex	OBJECT-TYPE
	SYNTAX	DisplayString 
	MAX-ACCESS	read-only 
	STATUS	current
	::=  {  persistenceEntry  1  }

persistenceDefaultHandling  OBJECT-TYPE
	SYNTAX	DisplayString 
	MAX-ACCESS	read-only 
	STATUS	current
	::=  {  persistenceEntry  2  }

persistenceGeoSiteId  OBJECT-TYPE
	SYNTAX	INTEGER 
	MAX-ACCESS	read-only 
	STATUS	current
	::=  {  persistenceEntry  3  }

persistenceGeoRemoteT3Url  OBJECT-TYPE
	SYNTAX	DisplayString 
	MAX-ACCESS	read-only 
	STATUS	current
	::=  {  persistenceEntry  4  }

persistenceDbEnabled  OBJECT-TYPE
	SYNTAX	DisplayString 
	MAX-ACCESS	read-only 
	STATUS	current
	::=  {  persistenceEntry  5  }

persistenceGeoEnabled  OBJECT-TYPE
	SYNTAX	DisplayString 
	MAX-ACCESS	read-only 
	STATUS	current
	::=  {  persistenceEntry  6  }

persistenceJmsSendAsIdentity  OBJECT-TYPE
	SYNTAX	DisplayString 
	MAX-ACCESS	read-only 
	STATUS	current
	::=  {  persistenceEntry  7  }


wlssTrapVars	OBJECT IDENTIFIER  ::=  {  wlss  100  }

wlssv1	OBJECT IDENTIFIER  ::=  {  wlss  200  }

wlssTrapServerName	OBJECT-TYPE 
	SYNTAX	DisplayString 
	MAX-ACCESS	read-only 
	STATUS	current
	::=  {  wlssTrapVars  1  }

wlssTrapAppName	OBJECT-TYPE 
	SYNTAX	DisplayString 
	MAX-ACCESS	read-only 
	STATUS	current
	DESCRIPTION
		"Sip Application name"
	::=  {  wlssTrapVars  2  }

wlssTrapErrorMsg	OBJECT-TYPE 
	SYNTAX	DisplayString 
	MAX-ACCESS	read-only 
	STATUS	current
	::=  {  wlssTrapVars  3  }

wlssTrapTime	OBJECT-TYPE 
	SYNTAX	DisplayString 
	MAX-ACCESS	read-only 
	STATUS	current
	::=  {  wlssTrapVars  4  }

wlssTrapLimit	OBJECT-TYPE 
	SYNTAX	INTEGER 
	MAX-ACCESS	read-only 
	STATUS	current
	::=  {  wlssTrapVars  5  }

wlssTrapPartitionName	OBJECT-TYPE 
	SYNTAX	DisplayString 
	MAX-ACCESS	read-only 
	STATUS	current
	::=  {  wlssTrapVars  6  }

wlssTrapReplicaName	OBJECT-TYPE 
	SYNTAX	DisplayString 
	MAX-ACCESS	read-only 
	STATUS	current
	::=  {  wlssTrapVars  7  }

wlssTrapServletName	OBJECT-TYPE 
	SYNTAX	DisplayString 
	MAX-ACCESS	read-only 
	STATUS	current
	::=  {  wlssTrapVars  8  }

sipAppDeployed	NOTIFICATION-TYPE
	OBJECTS	{ wlssTrapServerName , wlssTrapAppName , wlssTrapTime  }
	STATUS	current
	DESCRIPTION	"Sip application was deployed"
	REFERENCE	""
  ::=  {  wlssv1  1  }

sipAppUndeployed	NOTIFICATION-TYPE
	OBJECTS	{ wlssTrapServerName , wlssTrapAppName , wlssTrapTime  }
	STATUS	current
	DESCRIPTION	"Sip application was undeployed"
	REFERENCE	""
  ::=  {  wlssv1  2  }

sipAppFailedToDeploy	NOTIFICATION-TYPE
	OBJECTS	{ wlssTrapServerName , wlssTrapAppName , wlssTrapTime  }
	STATUS	current
	DESCRIPTION	"Sip Application Failed to deploy"
	REFERENCE	""
  ::=  {  wlssv1  3  }

overloadControlActivated	NOTIFICATION-TYPE
	OBJECTS	{ wlssTrapServerName , wlssTrapTime  }
	STATUS	current
	DESCRIPTION	"Overload control activated"
	REFERENCE	""
  ::=  {  wlssv1  4  }

overloadControlDeactivated	NOTIFICATION-TYPE
	OBJECTS	{ wlssTrapServerName , wlssTrapTime  }
	STATUS	current
	DESCRIPTION	"Ovlerload control deactivated"
	REFERENCE	""
  ::=  {  wlssv1  5  }

serverStopped	NOTIFICATION-TYPE
	OBJECTS	{ wlssTrapServerName , wlssTrapTime  }
	STATUS	current
	DESCRIPTION	"Notify about a clustered server failure"
	REFERENCE	""
  ::=  {  wlssv1  7  }

datatierServerStopped	NOTIFICATION-TYPE
	OBJECTS	{ wlssTrapServerName , wlssTrapTime  }
	STATUS	current
	DESCRIPTION	"Notify server when a server fails in a partition"
	REFERENCE	""
  ::=  {  wlssv1  8  }

replicaAddedToPartition	NOTIFICATION-TYPE
	OBJECTS	{ wlssTrapTime, wlssTrapServerName , wlssTrapPartitionName  }
	STATUS	current
	DESCRIPTION	"replica added to partition"
	REFERENCE	""
  ::=  {  wlssv1  9  }

replicaRemovedFromPartition	NOTIFICATION-TYPE
	OBJECTS	{ wlssTrapTime, wlssTrapServerName , wlssTrapPartitionName  }
	STATUS	current
	DESCRIPTION	"server removed from partition view"
	REFERENCE	""
  ::=  {  wlssv1  10  }

connectionLostToPeer	NOTIFICATION-TYPE
	OBJECTS	{ wlssTrapServerName , wlssTrapTime  }
	STATUS	current
	DESCRIPTION	"Connection lost to server"
	REFERENCE	""
  ::=  {  wlssv1  11  }

connectionReestablishedToPeer	NOTIFICATION-TYPE
	OBJECTS	{ wlssTrapServerName , wlssTrapTime  }
	STATUS	current
	DESCRIPTION	"Connection was reestablished to peer"
	REFERENCE	""
  ::=  {  wlssv1  12  }

replicaRemovedEnginesRegistration	NOTIFICATION-TYPE
	OBJECTS	{ wlssTrapServerName , wlssTrapReplicaName , wlssTrapTime  }
	STATUS	current
	DESCRIPTION	"As the replica removed engine registration info, engine is going to shut itself down as suggested by the engine"
	REFERENCE	""
  ::=  {  wlssv1  13  }

sipAppInfoTrap NOTIFICATION-TYPE
	OBJECTS	{ wlssTrapServerName , wlssTrapAppName, wlssTrapServletName, wlssTrapErrorMsg, wlssTrapTime  }
	STATUS	current
	DESCRIPTION	"Sip Application information trap Message"
	REFERENCE	""
  ::=  {  wlssv1  14  }

sipAppWarningTrap NOTIFICATION-TYPE
	OBJECTS	{ wlssTrapServerName , wlssTrapAppName, wlssTrapServletName, wlssTrapErrorMsg, wlssTrapTime  }
	STATUS	current
	DESCRIPTION	"Sip Application warning trap Message"
	REFERENCE	""
  ::=  {  wlssv1  15  }

sipAppErrorTrap NOTIFICATION-TYPE
	OBJECTS	{ wlssTrapServerName , wlssTrapAppName, wlssTrapServletName, wlssTrapErrorMsg, wlssTrapTime  }
	STATUS	current
	DESCRIPTION	"Sip Application error trap Message"
	REFERENCE	""
  ::=  {  wlssv1  16  }

sipAppNoticeTrap NOTIFICATION-TYPE
	OBJECTS	{ wlssTrapServerName , wlssTrapAppName, wlssTrapServletName, wlssTrapErrorMsg, wlssTrapTime  }
	STATUS	current
	DESCRIPTION	"Sip Application notice trap Message"
	REFERENCE	""
  ::=  {  wlssv1  17  }

sipAppCriticalTrap NOTIFICATION-TYPE
	OBJECTS	{ wlssTrapServerName , wlssTrapAppName, wlssTrapServletName, wlssTrapErrorMsg, wlssTrapTime  }
	STATUS	current
	DESCRIPTION	"Sip Application critical trap Message"
	REFERENCE	""
  ::=  {  wlssv1  18  }

sipAppAlertTrap NOTIFICATION-TYPE
	OBJECTS	{ wlssTrapServerName , wlssTrapAppName, wlssTrapServletName, wlssTrapErrorMsg, wlssTrapTime  }
	STATUS	current
	DESCRIPTION	"Sip Application alert trap Message"
	REFERENCE	""
  ::=  {  wlssv1  19  }

sipAppEmergencyTrap NOTIFICATION-TYPE
	OBJECTS	{ wlssTrapServerName , wlssTrapAppName, wlssTrapServletName, wlssTrapErrorMsg, wlssTrapTime  }
	STATUS	current
	DESCRIPTION	"Sip Application emergency trap Message"
	REFERENCE	""
  ::=  {  wlssv1  20  }

databaseError NOTIFICATION-TYPE
	OBJECTS	{ wlssTrapServerName , wlssTrapErrorMsg, wlssTrapTime  }
	STATUS	current
	DESCRIPTION	"Sip Application error trap Message"
	REFERENCE	""
  ::=  {  wlssv1  21  }

invalidWlssConfiguration NOTIFICATION-TYPE
	OBJECTS	{ wlssTrapServerName , wlssTrapTime, wlssTrapErrorMsg  }
	STATUS	current
	DESCRIPTION	"WLSS configuration is invalid"
	REFERENCE	""
  ::=  {  wlssv1  23  }

END
